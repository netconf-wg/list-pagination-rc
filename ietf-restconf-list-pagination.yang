module ietf-restconf-list-pagination {
  namespace
    "urn:ietf:params:xml:ns:yang:ietf-restconf-list-pagination";
  prefix rlpg;

  import ietf-restconf {
    prefix rc;
    reference "RFC 8040: RESTCONF Protocol";
  }

  organization
    "IETF NETCONF (Network Configuration) Working Group";

  contact
    "WG Web:   <http://tools.ietf.org/wg/netconf/>
     WG List:  <mailto:netconf@ietf.org>";

  description
    "This module is used be RESTCONF servers to indicate that
     they support pagination on 'list' and 'leaf-list' resources.

     Copyright (c) 2015 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

  revision YYYY-MM-DD {
    description
      "Initial revision.";
    reference
      "RFC XXXX: RESTCONF Extensions to Support List Pagination";
  }

}
